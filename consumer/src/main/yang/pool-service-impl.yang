module pool-service-impl{

    yang-version 1;
    namespace "urn:opendaylight:params:xml:ns:yang:pool-service:impl";
    prefix "pool-service-impl";

    import config { prefix config; revision-date 2013-04-05; }
    import rpc-context { prefix rpcx; revision-date 2013-06-17; }

    import opendaylight-md-sal-binding { prefix mdsal; revision-date 2013-10-28; }

    description
        "This module contains the base YANG definitions for
        pool-service impl implementation.";

    revision "2014-01-31" {
        description
            "Initial revision.";
    }

    // This is the definition of pool service interface identity.
    identity pool-service {
        base "config:service-type";
        config:java-class "org.opendaylight.jacuzzi.consumer.api.PoolService";
    }

    // This is the definition of kitchen service implementation module identity. 
    identity pool-service-impl {
            base "config:module-type";
            config:provided-service pool-service;
            config:java-name-prefix PoolService;
    }

    augment "/config:modules/config:module/config:configuration" {
        case pool-service-impl {
            when "/config:modules/config:module/config:type = 'pool-service-impl'";

            container rpc-registry {
                uses config:service-ref {
                    refine type {
                        mandatory true;
                        config:required-identity mdsal:binding-rpc-registry;
                    }
                }
            }
            container notification-service {
               uses config:service-ref {
                   refine type {
                       mandatory true;
                       config:required-identity mdsal:binding-notification-service;
                   }
               }
           }
        }
    }
    augment "/config:modules/config:module/config:state" {
        case pool-service-impl {
            when "/config:modules/config:module/config:type = 'pool-service-impl'";

            rpcx:rpc-context-instance "make-spa-rpc";
        }
    }

    identity make-spa-rpc;

    rpc make-spa  {
        description
          "Shortcut JMX call to setup all the spa.";

        input {
            uses rpcx:rpc-context-ref {
                refine context-instance {
                    rpcx:rpc-context-instance make-spa-rpc;
                }
            }
        }
        output {
            leaf result {
                type boolean;
            }
        }
    }
}
